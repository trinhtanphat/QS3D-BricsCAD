(vl-load-com)
(setq qs021-before-ok nil qs021-after-ok nil)
(defun qs021-geometry (expected top / ss obj lo hi)
  (setq ss (ssget "_X" '((0 . "3DSOLID"))))
  (if (/= (if ss (sslength ss) 0) 1) (error "Expected exactly one native solid"))
  (setq obj (vlax-ename->vla-object (ssname ss 0)))
  (if (> (abs (- (/ (vla-get-Volume obj) 1e9) expected)) 1e-7) (error "Native volume mismatch"))
  (vla-GetBoundingBox obj 'lo 'hi)
  (setq lo (vlax-safearray->list lo) hi (vlax-safearray->list hi))
  (if (not (and (equal lo '(0.0 0.0 0.0) 1e-5) (equal hi (list 4000.0 6000.0 top) 1e-5))) (error "Native bounds mismatch"))
  (list ss obj lo hi))
(defun qs021-check-after (/ sources)
  (qs021-geometry 19.2 800.0)
  (setq sources (ssget "_X" '((0 . "LWPOLYLINE"))))
  (if (/= (if sources (sslength sources) 0) 2) (error "Source cardinality mismatch"))
  (princ "\nLOCAL021_NATIVE_800_GEOMETRY_ASSERTIONS_PASS"))
(defun qs021-before ()
  (setq qs021-before-ok nil qs021-after-ok nil)
  (setq qs021-before-state (qs021-geometry 21.6 900.0))
  (setq qs021-old-handle (vla-get-Handle (cadr qs021-before-state)))
  (sssetfirst nil (car qs021-before-state))
  (setq qs021-before-ok T)
  (princ "\nLOCAL021_RECOVERED_900_ASSERTIONS_PASS"))
(defun qs021-after ()
  (setq qs021-after-ok nil)
  (if (not qs021-before-ok) (error "Before assertions incomplete"))
  (qs021-check-after)
  (if (and (handent qs021-old-handle) (entget (handent qs021-old-handle))) (error "Old generated solid still live"))
  (setq qs021-after-ok T)
  (princ "\nLOCAL021_REPLACEMENT_ASSERTIONS_PASS"))
(defun qs021-run-phase (phase)
  (if (= phase "rebuild")
    (progn
      (qs021-before)
      (command "QS3DBUILD3D")
      (qs021-after)
      (command "QS3DSAVE")
      (command "_.QSAVE"))
    (if (= phase "cold") (qs021-check-after) (error "Unknown phase")))
  (if (/= (getvar "DBMOD") 0) (error "Drawing not saved")))
(defun qs021-write-result (phase / result out)
  (setq result (vl-catch-all-apply 'qs021-run-phase (list phase)))
  (setq out (open (getenv "QS3D_LOCAL021_RESULT") "w"))
  (if (null out) (error "Cannot write result"))
  (if (vl-catch-all-error-p result)
    (progn
      (princ (strcat "\nLOCAL021_FAILURE: " (vl-catch-all-error-message result)))
      (write-line (strcat "{\"status\":\"FAIL\",\"phase\":\"" phase "\",\"run_id\":\"" (getenv "QS3D_LOCAL021_RUN_ID") "\"}") out))
    (write-line (strcat "{\"status\":\"PASS\",\"phase\":\"" phase "\",\"run_id\":\"" (getenv "QS3D_LOCAL021_RUN_ID") "\",\"solid_count\":1,\"source_polyline_count\":2,\"volume_m3\":19.2,\"bottom_z_mm\":0,\"top_z_mm\":800}") out))
  (close out)
  (princ))
(princ)
